;;;Two Point Leader Arrow
(defun c:twopointa()
	(command "twopoint" "a")
	(princ)
)
;;;Two Point Leader Blank Dot
(defun c:twopointb()
	(command "twopoint" "b")
	(princ)
)

;;;Two Point Leader dot
(defun c:twopointd()
	(command "twopoint" "d")
	(princ)
)

;;;Two Point Leader Integral
(defun c:twopointi()
	(command "twopoint" "i")
	(princ)
)

;;;three Point Leader Arrow
(defun c:threepointa()
	(command "threepoint" "a")
	(princ)
)
;;;threePoint Leader Blank Dot
(defun c:threepointb()
	(command "threepoint" "b")
	(princ)
)

;;;Three Point Leader dot
(defun c:threepointd()
	(command "threepoint" "d")
	(princ)
)

;;;Three Point Leader Integral
(defun c:threepointi()
	(command "threepoint" "i")
	(princ)
)
