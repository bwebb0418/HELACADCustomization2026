;;;10M Bar Block Insertion Command
(defun C:10M()
	(command "rebar" "10M")
	(princ)
)
;;;15M Bar Block Insertion Command
(defun C:15M()
	(command "rebar" "15M")
	(princ)
)
;;;20M Bar Block Insertion Command
(defun C:20M()
	(command "rebar" "20M")
	(princ)
)
;;;25M Bar Block Insertion Command
(defun C:25M()
	(command "rebar" "25M")
	(princ)
)
;;;30M Bar Block Insertion Command
(defun C:30M()
	(command "rebar" "30M")
	(princ)
)
;;;35M Bar Block Insertion Command
(defun C:35M()
	(command "rebar" "35M")
	(princ)
)
;;;45M Bar Block Insertion Command
(defun C:45M()
	(command "rebar" "45M")
	(princ)
)
;;;55M Bar Block Insertion Command
(defun C:55M()
	(command "rebar" "55M")
	(princ)
)
