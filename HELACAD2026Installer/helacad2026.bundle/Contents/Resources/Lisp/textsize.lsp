;;;2.0mm Text Command
(defun C:20mm()
	(command "-vbarun" "text.text" "20")
	(princ)
)
;;;2.5mm Text Command
(defun C:25mm()
	(command "-vbarun" "text.text" "25")
	(princ)
)
;;;3mm Text Command
(defun C:30mm()
	(command "-vbarun" "text.text" "30")
	(princ)
)
;;;3.5mm Text Command
(defun C:35mm()
	(command "-vbarun" "text.text" "35")
	(princ)
)
;;;4mm Text Command
(defun C:40mm()
	(command "-vbarun" "text.text" "40")
	(princ)
)
;;;5mm Text Command
(defun C:50mm()
	(command "-vbarun" "text.text" "50")
	(princ)
)
